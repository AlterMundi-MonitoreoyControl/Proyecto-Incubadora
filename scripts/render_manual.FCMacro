"""Renderiza vistas del FCStd existente sin modificarlo ni guardarlo.

Ejecutar con FreeCAD: definir LIBREINCU_FCSTD y LIBREINCU_RENDER_DIR.
Las capturas conservan la geometría y las posiciones del documento.
Con LIBREINCU_KEEP_OPEN=1 no cierra FreeCAD al terminar (uso desde el bridge MCP).
"""
import os
import json
import hashlib
from pathlib import Path
import FreeCAD as App
import FreeCADGui as Gui
from PySide import QtCore, QtGui

source = Path(os.environ['LIBREINCU_FCSTD'])
source_sha256 = hashlib.sha256(source.read_bytes()).hexdigest()
output = Path(os.environ['LIBREINCU_RENDER_DIR'])
output.mkdir(parents=True, exist_ok=True)
doc = App.openDocument(str(source))
view = Gui.activeDocument().activeView()
view.setCameraType('Orthographic')
# Sin animación: los cambios de vista animados no terminan antes del encuadre.
animated=view.isAnimationEnabled()
view.setAnimationEnabled(False)
Gui.getMainWindow().resize(1400,1100)
Gui.activateWorkbench('PartWorkbench')
features = [o for o in doc.Objects if o.TypeId == 'Part::Feature']
root=doc.getObject('despiece_libreincu')
for o in doc.Objects:
    if o.ViewObject:
        if o.TypeId == 'App::Part':
            o.ViewObject.Visibility=True
        elif o.TypeId != 'Part::Feature':
            o.ViewObject.Visibility=False
manifest=[]

GREY=(0.70,0.74,0.77)
COLORS=[  # prefijo del nombre de la pieza: color
    ('soporte_',(0.18,0.40,0.56)),
    (('bandeja_','cuna_brazo_'),(0.83,0.67,0.30)),
    ('acople_',(0.25,0.48,0.42)),
    ('deflector_',(0.62,0.66,0.70)),
    ('carro_',(0.45,0.46,0.50)),
    ('dos_finales_',(0.15,0.15,0.18)),
    ('dos_reed',(0.16,0.55,0.55)),
    ('fc_bandeja_agua',(0.82,0.84,0.87)),
    ('fc_contraplaca',(0.33,0.35,0.38)),
    ('fc_resistencia',(0.78,0.32,0.22)),
    (('fc_fusible','fc_remache'),(0.90,0.66,0.12)),
    ('fc_perfil_L',(0.18,0.40,0.56)),
    ('fc_soporte_nacedora',(0.11,0.27,0.40)),
    ('fc_chapa_impacto',(0.56,0.71,0.84)),
    ('camara_',(0.86,0.86,0.86)),
]

def color_of(name):
    for prefix,color in COLORS:
        if name.startswith(prefix):
            return color
    return GREY

def leaves(groups, exclude=()):
    """Piezas contenidas en los grupos (a cualquier profundidad)."""
    found=set()
    stack=[doc.getObject(g) for g in groups]
    while stack:
        obj=stack.pop()
        if obj is None:
            continue
        if obj.TypeId == 'Part::Feature':
            found.add(obj.Name)
        else:
            stack.extend(getattr(obj,'Group',[]))
    return found - set(exclude)

def wall(test):
    """Pared de la cámara de referencia que cumple test(BoundBox global)."""
    for o in sorted(leaves(['camara_referencia'])):
        obj=doc.getObject(o)
        shape=obj.Shape.copy()
        shape.Placement=obj.getGlobalPlacement().multiply(obj.Placement.inverse()).multiply(shape.Placement)
        if test(shape.BoundBox):
            return o
    raise RuntimeError('Pared no encontrada')

def below(rot):
    """Misma vista axonométrica, mirando desde abajo y con Z hacia arriba en pantalla."""
    for sign in (1,-1):
        cand = rot.multiply(App.Rotation(App.Vector(1,0,0), sign*70.5288))
        if cand.multVec(App.Vector(0,0,-1)).z > 0 and cand.multVec(App.Vector(0,1,0)).z > 0:
            return cand
    raise RuntimeError('No se pudo orientar la vista inferior')

def fit_visible(names, margin=1.04):
    """Encuadra solo las piezas visibles: fitAll también cuenta las ocultas."""
    rot=view.getCameraOrientation()
    axes=[rot.multVec(App.Vector(*v)) for v in ((1,0,0),(0,1,0),(0,0,-1))]
    lo,hi=[1e18]*3,[-1e18]*3
    for n in names:
        obj=doc.getObject(n)
        shape=obj.Shape.copy()
        shape.Placement=obj.getGlobalPlacement().multiply(obj.Placement.inverse()).multiply(shape.Placement)
        b=shape.BoundBox
        for x in (b.XMin,b.XMax):
            for y in (b.YMin,b.YMax):
                for z in (b.ZMin,b.ZMax):
                    for i,a in enumerate(axes):
                        d=App.Vector(x,y,z).dot(a)
                        lo[i],hi[i]=min(lo[i],d),max(hi[i],d)
    vw,vh=view.getSize()
    cam=view.getCameraNode()
    center=axes[0]*((lo[0]+hi[0])/2)+axes[1]*((lo[1]+hi[1])/2)+axes[2]*(lo[2]-1000)
    cam.position.setValue(center.x,center.y,center.z)
    du,dv,aspect=hi[0]-lo[0],hi[1]-lo[1],vw/vh
    # Coin aplica height al lado más corto de la imagen.
    cam.height.setValue((max(dv,du/aspect) if aspect>=1 else max(du,dv*aspect))*margin)
    cam.nearDistance.setValue(1)
    cam.farDistance.setValue(hi[2]-lo[2]+2000)

def capture(name, groups, angle='iso', size=(1400,1000), extra=(), exclude=()):
    visible=leaves(groups, exclude) | set(extra)
    for o in features:
        o.ViewObject.Visibility = o.Name in visible
        o.ViewObject.DisplayMode='Flat Lines'
        o.ViewObject.LineWidth=1.0
        color=color_of(o.Name)
        o.ViewObject.ShapeColor=color
        o.ViewObject.DiffuseColor=[color] * len(o.Shape.Faces)
    width,height = size
    Gui.getMainWindow().resize(width,height)
    Gui.updateGui()
    if angle == 'front':
        view.viewRear()
    elif angle == 'side':
        view.viewLeft()
    elif angle == 'iso-below':
        view.viewAxonometric()
        view.setCameraOrientation(below(view.getCameraOrientation()))
    else:
        view.viewAxonometric()
    Gui.updateGui()
    fit_visible(visible)
    Gui.updateGui()
    # La ventana no siempre llega al tamaño pedido (pantallas de 1080 px):
    # guardar con la proporción real del visor para no deformar el encuadre.
    vw,vh = view.getSize()
    k = max(width/vw, height/vh)
    width,height = int(vw*k), int(vh*k)
    path = output/(name+'.png')
    view.saveImage(str(path),width,height,'White')
    # Extraer el área de geometría de la captura, conservando sus píxeles.
    image = QtGui.QImage(str(path))
    left,top,right,bottom = width,height,-1,-1
    for y in range(height):
        for x in range(width):
            if (image.pixel(x,y) & 0xffffff) != 0xffffff:
                left,top = min(left,x),min(top,y)
                right,bottom = max(right,x),max(bottom,y)
    if right < left:
        raise RuntimeError('Captura vacía: '+name)
    margin = 30
    left,top = max(0,left-margin),max(0,top-margin)
    right,bottom = min(width,right+margin+1),min(height,bottom+margin+1)
    image.copy(left,top,right-left,bottom-top).save(str(path))
    manifest.append({'archivo':name+'.png','componentes':list(groups)+sorted(extra),'excluidos':list(exclude),
                     'camara':angle,'fuente':source.name,'sha256_fuente':source_sha256})

tray_groups=[o.Name for o in root.Group if o.Name.startswith(('bandeja_', 'eje_bandeja_', 'soporte_KL08_', 'cuna_brazo_'))]
screw_groups=['husillo_8mm_400mm','soporte_KP08_superior','soporte_KP08_inferior','acople_8x8_motor']
water=('fc_agua_referencia',)
capture('bandejas-y-soportes',tray_groups)
capture('husillo-kp08-acople',screw_groups,size=(800,1400))
# Corte lateral con el fondo y el piso como referencia de las cotas de 60 y 300 mm.
floor=wall(lambda b: b.ZMax <= 0.5 and b.ZMin < -1)
back=wall(lambda b: b.YMax <= 0.5 and b.YMin < -1)
capture('corte-lateral',['deflector_inferior_bandejas_0p5mm','fuente_calor','plenum_superior_ventilador']
        +[g for g in tray_groups if not g.endswith('_izquierda')],angle='side',extra=(floor,back),exclude=water)
capture('fuente-de-calor',['fuente_calor'],exclude=water)
capture('fuente-de-calor-inferior',['fuente_calor'],angle='iso-below',exclude=water)
reeds=['dos_reed'] if doc.getObject('dos_reed') is not None else []
capture('carro-y-finales-de-carrera',['carro_plegado_corredera_perno','dos_finales_de_carrera','husillo_8mm_400mm',
        'soporte_KP08_superior','soporte_KP08_inferior']+reeds,size=(800,1400))
(output/'vistas.json').write_text(json.dumps(manifest,ensure_ascii=False,indent=2)+'\n')
view.setAnimationEnabled(animated)
App.closeDocument(doc.Name)
if not os.environ.get('LIBREINCU_KEEP_OPEN'):
    QtCore.QTimer.singleShot(0,Gui.getMainWindow().close)
